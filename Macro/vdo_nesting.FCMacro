#!/usr/bin/env python
# -*- coding: utf-8 -*-
"""
vdo_nesting.FCMacro
Optimizador de Corte Automático (Nesting) para VDO
Integración con Nesting Workbench de FreeCAD

Uso:
  1. Selecciona modo: TODO, SELECCIÓN, GRUPO
  2. Configura tablero: tamaño, espaciado
  3. Ejecuta nesting
  4. Visualiza resultado automáticamente
"""

import sys
import os
from pathlib import Path

# Asegurar que el directorio de macros está en el path
_macro_dir = Path(__file__).parent
if str(_macro_dir) not in sys.path:
    sys.path.insert(0, str(_macro_dir))

import vdo_nesting_workflow

# Ejecutar
vdo_nesting_workflow.main()
