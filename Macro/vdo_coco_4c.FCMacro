# -*- coding: utf-8 -*-
# =====================================================================
# vdo_coco_4c.FCMacro
# Envoltorio para COCO 4C con FeaturePython y Editor Unificado
# =====================================================================

import sys
import FreeCAD as App

_vdo_macro_dir = App.getUserMacroDir(True)
if _vdo_macro_dir not in sys.path:
    sys.path.insert(0, _vdo_macro_dir)

from vdo_creation_flow import crear_modulo_interactivo

configuracion = {
    # Los valores omitidos se toman de vdo_module_specs.py
    "nombre": "COCO_4C",
}

# Flujo VDO: crear oculto → panel de configuración → colocar con clic.
# También se puede editar después con clic derecho o doble clic.
crear_modulo_interactivo("coco_4c", configuracion)
