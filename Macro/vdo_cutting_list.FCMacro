#!/usr/bin/env python
# -*- coding: utf-8 -*-
"""
vdo_cutting_list.FCMacro
Launcher para exportar lista de corte con preview visual

Menú: Selecciona modo → Preview (colorea en rojo) → Confirma → CSV
"""

import sys
from pathlib import Path

macro_dir = Path(__file__).parent
sys.path.insert(0, str(macro_dir))

try:
    import FreeCAD as App
    import FreeCADGui as Gui
    try:
        from PySide2 import QtWidgets
    except ImportError:
        from PySide import QtWidgets
except Exception:
    print("❌ Este script requiere FreeCAD + PySide (Qt)")
    sys.exit(1)

import vdo_cutting_list_preview


def mostrar_menu():
    """Muestra diálogo para elegir modo de exportación"""

    dialog = QtWidgets.QDialog()
    dialog.setWindowTitle("📊 VDO - Exportar Lista de Corte")
    dialog.setMinimumWidth(400)

    layout = QtWidgets.QVBoxLayout()

    # Título
    titulo = QtWidgets.QLabel("¿Qué piezas deseas exportar?")
    titulo.setStyleSheet("font-size: 14px; font-weight: bold;")
    layout.addWidget(titulo)

    layout.addSpacing(10)

    # Opciones
    radio_todo = QtWidgets.QRadioButton("📋 EXPORTAR TODO el documento")
    radio_seleccion = QtWidgets.QRadioButton("✋ EXPORTAR SELECCIÓN (objetos marcados)")
    radio_grupo = QtWidgets.QRadioButton("📦 EXPORTAR MÓDULO actual")

    # Preseleccionar SELECCIÓN si hay objetos marcados en el árbol/3D
    if Gui.Selection.getSelection():
        radio_seleccion.setChecked(True)
    else:
        radio_todo.setChecked(True)

    layout.addWidget(radio_todo)
    layout.addWidget(radio_seleccion)
    layout.addWidget(radio_grupo)

    layout.addSpacing(15)

    # Info
    info = QtWidgets.QLabel(
        "ℹ️ Se exportarán SOLO paneles de melamina\n"
        "   (Se excluyen muros, paneles BIM, etc)\n\n"
        "El siguiente paso mostrará un PREVIEW\n"
        "con las piezas coloreadas en ROJO para confirmar"
    )
    info.setStyleSheet("color: #666; font-size: 11px;")
    layout.addWidget(info)

    layout.addSpacing(15)

    # Botones
    btn_layout = QtWidgets.QHBoxLayout()

    btn_cancelar = QtWidgets.QPushButton("Cancelar")
    btn_cancelar.clicked.connect(dialog.reject)
    btn_layout.addWidget(btn_cancelar)

    btn_ok = QtWidgets.QPushButton("Continuar →")
    btn_ok.setStyleSheet("background-color: #0066cc; color: white; font-weight: bold;")
    btn_ok.clicked.connect(dialog.accept)
    btn_layout.addWidget(btn_ok)

    layout.addLayout(btn_layout)

    dialog.setLayout(layout)

    # Mostrar y obtener resultado
    if dialog.exec_() != QtWidgets.QDialog.Accepted:
        print("❌ Cancelado")
        return None

    # Determinar modo seleccionado
    if radio_seleccion.isChecked():
        return "seleccion"
    elif radio_grupo.isChecked():
        return "grupo"
    else:
        return "todo"


def main():
    print("=" * 70)
    print("🚀 VDO CUTTING LIST - Exportador con Preview")
    print("=" * 70)

    doc = App.ActiveDocument
    if not doc:
        print("❌ No hay documento activo")
        return

    # Mostrar menú
    modo = mostrar_menu()
    if not modo:
        return

    print(f"\n📌 Modo seleccionado: {modo.upper()}")

    # Iniciar preview
    vdo_cutting_list_preview.main(modo=modo)


if __name__ == "__main__":
    main()
