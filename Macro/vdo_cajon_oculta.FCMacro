# -*- coding: utf-8 -*-
# =====================================================================
# vdo_cajon_oculta.FCMacro
# Envoltorio del cajón con corredera oculta (Blum Tandem etc)
# Axioma 3: Capa UI - solo parámetros de configuración
# =====================================================================

import sys
import FreeCAD as App

_vdo_macro_dir = App.getUserMacroDir(True)
if _vdo_macro_dir not in sys.path:
    sys.path.insert(0, _vdo_macro_dir)

from vdo_creation_flow import crear_modulo_interactivo

configuracion = {
    "nombre": "Cajon_Oculta",
    # Los valores omitidos se toman de vdo_module_specs.py
}

# Flujo VDO: crear oculto → panel de configuración → colocar con clic.
crear_modulo_interactivo("cajon_oculta", configuracion)
