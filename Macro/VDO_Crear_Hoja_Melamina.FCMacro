# -*- coding: utf-8 -*-
# =====================================================================
# VDO_Crear_Hoja_Melamina
# La creación de la hoja global la gestiona ahora el Guardián de
# Dependencias. Esta macro se mantiene por compatibilidad y delega
# en vdo_guardian.vdo_guard().
# =====================================================================

import FreeCAD as App
import sys

# Bootstrap: habilita la importación de los módulos VDO (carpeta de macros)
_vdo_macro_dir = App.getUserMacroDir(True)
if _vdo_macro_dir not in sys.path:
    sys.path.insert(0, _vdo_macro_dir)

import vdo_guardian

# El Guardián garantiza la hoja global 'Params_Melamina' y la local 'Params'.
vdo_guardian.vdo_guard()

print("🎉 Entorno VDO listo: [Params_Melamina] y [Params] garantizados por el Guardián.")
