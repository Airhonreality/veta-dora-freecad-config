# -*- coding: utf-8 -*-
# =====================================================================
# vdo_panel_division.FCMacro
# Envoltorio ultraligero para Panel División (panel orientado verticalmente)
# Axioma 3: Capa UI - solo parámetros (sin acoplar semántica)
# =====================================================================

import sys
import FreeCAD as App

# Bootstrap
_vdo_macro_dir = App.getUserMacroDir(True)
if _vdo_macro_dir not in sys.path:
    sys.path.insert(0, _vdo_macro_dir)

from vdo_creation_flow import crear_modulo_interactivo

# Configuración física (orientación libre, sin semántica de mobiliario)
configuracion = {
    "nombre": "Division_1",
    "etiqueta": "División",
    "orientacion": "vertical",
    "cantos": {
        "norte": "FX",
        "sur": "FX",
        "este": "FX",
        "oeste": "FX",
    },
    "material_ref": "melamina_standar",
}

crear_modulo_interactivo("panel_division", configuracion)
